module NSO-SANDBOX {

  namespace "http://example.com/NSO-SANDBOX";
  prefix NSO-SANDBOX;

  import ietf-inet-types {
    prefix inet;
  }
  import tailf-common {
    prefix tailf;
  }
  import tailf-ncs {
    prefix ncs;
  }

  description
    "Bla bla...";

  revision 2016-01-01 {
    description
      "Initial revision.";
  }

  list NSO-SANDBOX {
    description "This is an RFS skeleton service";

    key name;
    leaf name {
      tailf:info "Unique service id";
      tailf:cli-allow-range;
      type string;
    }

    uses ncs:service-data;
    ncs:servicepoint NSO-SANDBOX-servicepoint;

    // may replace this with other ways of refering to the devices.
    list svi {
      key vlan-id;
      leaf vlan-id {
        tailf:info "VLAN ID";
        type int32;
        range "2..4096";
      }
    }


  }
}
